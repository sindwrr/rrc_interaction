RRCSetup DEFINITIONS AUTOMATIC TAGS ::= BEGIN

RRCConnectionSetup ::= SEQUENCE {
    rrc-TransactionIdentifier RRC-TransactionIdentifier,
    rrcConnectionSetup-r8 RRCConnectionSetup-r8-IEs
}

RRC-TransactionIdentifier ::= INTEGER (0..3)

RRCConnectionSetup-r8-IEs ::= SEQUENCE {
    lateNonCriticalExtension OCTET STRING OPTIONAL,
    nonCriticalExtension SEQUENCE {} OPTIONAL
}

END
